rpmModule
  { iso(1) org(3) dod(6) internet(1) private(4) enterprise(1) rpm(36106) }

DEFINITIONS EXPLICIT TAGS ::=
BEGIN

id-rpm-tag OBJECT IDENTIFIER ::=
  { iso(1) org(3) dod(6) internet(1) private(4) enterprise(1)
		rpm(36106) tag(1) }

-- FIXME: these are not right and should be in libtasn1 not here
UTF8String            ::= [UNIVERSAL 12] IMPLICIT OCTET STRING
NumericString         ::= [UNIVERSAL 18] IMPLICIT OCTET STRING
PrintableString       ::= [UNIVERSAL 19] IMPLICIT OCTET STRING
TeletexString         ::= [UNIVERSAL 20] IMPLICIT OCTET STRING
T61String             ::= [UNIVERSAL 20] IMPLICIT OCTET STRING
VideotexString        ::= [UNIVERSAL 21] IMPLICIT OCTET STRING
IA5String             ::= [UNIVERSAL 22] IMPLICIT OCTET STRING
-- UTCTime               ::= [UNIVERSAL 23] IMPLICIT OCTET STRING
-- GeneralizedTime       ::= [UNIVERSAL 24] IMPLICIT OCTET STRING
GraphicString         ::= [UNIVERSAL 25] IMPLICIT OCTET STRING
VisibleString         ::= [UNIVERSAL 26] IMPLICIT OCTET STRING
ISO646String          ::= [UNIVERSAL 26] IMPLICIT OCTET STRING
-- GeneralString         ::= [UNIVERSAL 27] IMPLICIT OCTET STRING
UniversalString       ::= [UNIVERSAL 28] IMPLICIT OCTET STRING
BMPString             ::= [UNIVERSAL 30] IMPLICIT OCTET STRING

-- RPM tag data primitive types
RPM_UINT8_TYPE        ::= INTEGER (0..255)
RPM_UINT16_TYPE       ::= INTEGER (0..65535)
RPM_UINT32_TYPE       ::= INTEGER (0..4294967295)
RPM_UINT64_TYPE       ::= INTEGER (0..18446744073709551615)
RPM_STRING_TYPE       ::= VisibleString
RPM_BIN_TYPE          ::= OCTET STRING
RPM_STRING_ARRAY_TYPE ::= VisibleString
RPM_I18NSTRING_TYPE   ::= UTF8String

-- RPM tag data new types
RPM_UTCTIME_TYPE      ::= [UNIVERSAL 23] IMPLICIT OCTET STRING
RPM_TIME_TYPE         ::= [UNIVERSAL 24] IMPLICIT OCTET STRING

-- RPM tag OIDs and data typing
id-rpm-tag-Name	OBJECT_IDENTIFIER ::= { id-rpm-tag 1000 }
Name ::= RPM_STRING_TYPE

id-rpm-tag-Version	OBJECT_IDENTIFIER ::= { id-rpm-tag 1001 }
Version ::= RPM_STRING_TYPE

id-rpm-tag-Release	OBJECT_IDENTIFIER ::= { id-rpm-tag 1002 }
Release ::= RPM_STRING_TYPE

id-rpm-tag-Epoch	OBJECT_IDENTIFIER ::= { id-rpm-tag 1003 }
Epoch ::= RPM_UINT32_TYPE

id-rpm-tag-Summary	OBJECT_IDENTIFIER ::= { id-rpm-tag 1004 }
Summary ::= RPM_I18NSTRING_TYPE

id-rpm-tag-Description	OBJECT_IDENTIFIER ::= { id-rpm-tag 1005 }
Description ::= RPM_I18NSTRING_TYPE

id-rpm-tag-Buildtime	OBJECT_IDENTIFIER ::= { id-rpm-tag 1006 }
Buildtime ::= RPM_UTCTIME_TYPE

id-rpm-tag-Buildhost	OBJECT_IDENTIFIER ::= { id-rpm-tag 1007 }
Buildhost ::= RPM_STRING_TYPE

id-rpm-tag-Installtime	OBJECT_IDENTIFIER ::= { id-rpm-tag 1008 }
Installtime ::= SEQUENCE OF RPM_UINT32_TYPE

id-rpm-tag-Size	OBJECT_IDENTIFIER ::= { id-rpm-tag 1009 }
Size ::= RPM_UINT32_TYPE

id-rpm-tag-Distribution	OBJECT_IDENTIFIER ::= { id-rpm-tag 1010 }
Distribution ::= RPM_STRING_TYPE

id-rpm-tag-Vendor	OBJECT_IDENTIFIER ::= { id-rpm-tag 1011 }
Vendor ::= RPM_STRING_TYPE

id-rpm-tag-Gif	OBJECT_IDENTIFIER ::= { id-rpm-tag 1012 }
Gif ::= RPM_BIN_TYPE

id-rpm-tag-Xpm	OBJECT_IDENTIFIER ::= { id-rpm-tag 1013 }
Xpm ::= RPM_BIN_TYPE

id-rpm-tag-License	OBJECT_IDENTIFIER ::= { id-rpm-tag 1014 }
License ::= RPM_STRING_TYPE

id-rpm-tag-Packager	OBJECT_IDENTIFIER ::= { id-rpm-tag 1015 }
Packager ::= RPM_STRING_TYPE

id-rpm-tag-Group	OBJECT_IDENTIFIER ::= { id-rpm-tag 1016 }
Group ::= RPM_I18NSTRING_TYPE

id-rpm-tag-Source	OBJECT_IDENTIFIER ::= { id-rpm-tag 1018 }
Source ::= SEQUENCE OF RPM_STRING_ARRAY_TYPE

id-rpm-tag-Patch	OBJECT_IDENTIFIER ::= { id-rpm-tag 1019 }
Patch ::= SEQUENCE OF RPM_STRING_ARRAY_TYPE

id-rpm-tag-Url	OBJECT_IDENTIFIER ::= { id-rpm-tag 1020 }
Url ::= RPM_STRING_TYPE

id-rpm-tag-Os	OBJECT_IDENTIFIER ::= { id-rpm-tag 1021 }
Os ::= RPM_STRING_TYPE

id-rpm-tag-Arch	OBJECT_IDENTIFIER ::= { id-rpm-tag 1022 }
Arch ::= RPM_STRING_TYPE

id-rpm-tag-Prein	OBJECT_IDENTIFIER ::= { id-rpm-tag 1023 }
Prein ::= RPM_STRING_TYPE

id-rpm-tag-Postin	OBJECT_IDENTIFIER ::= { id-rpm-tag 1024 }
Postin ::= RPM_STRING_TYPE

id-rpm-tag-Preun	OBJECT_IDENTIFIER ::= { id-rpm-tag 1025 }
Preun ::= RPM_STRING_TYPE

id-rpm-tag-Postun	OBJECT_IDENTIFIER ::= { id-rpm-tag 1026 }
Postun ::= RPM_STRING_TYPE

id-rpm-tag-Oldfilenames	OBJECT_IDENTIFIER ::= { id-rpm-tag 1027 }
Oldfilenames ::= SEQUENCE OF RPM_STRING_ARRAY_TYPE

id-rpm-tag-Filesizes	OBJECT_IDENTIFIER ::= { id-rpm-tag 1028 }
Filesizes ::= SEQUENCE OF RPM_UINT32_TYPE

id-rpm-tag-Filestates	OBJECT_IDENTIFIER ::= { id-rpm-tag 1029 }
Filestates ::= SEQUENCE OF RPM_UINT8_TYPE

id-rpm-tag-Filemodes	OBJECT_IDENTIFIER ::= { id-rpm-tag 1030 }
Filemodes ::= SEQUENCE OF RPM_UINT16_TYPE

id-rpm-tag-Filerdevs	OBJECT_IDENTIFIER ::= { id-rpm-tag 1033 }
Filerdevs ::= SEQUENCE OF RPM_UINT16_TYPE

id-rpm-tag-Filemtimes	OBJECT_IDENTIFIER ::= { id-rpm-tag 1034 }
Filemtimes ::= SEQUENCE OF RPM_UTCTIME_TYPE

id-rpm-tag-Filedigests	OBJECT_IDENTIFIER ::= { id-rpm-tag 1035 }
Filedigests ::= SEQUENCE OF RPM_STRING_ARRAY_TYPE

id-rpm-tag-Filelinktos	OBJECT_IDENTIFIER ::= { id-rpm-tag 1036 }
Filelinktos ::= SEQUENCE OF RPM_STRING_ARRAY_TYPE

id-rpm-tag-Fileflags	OBJECT_IDENTIFIER ::= { id-rpm-tag 1037 }
Fileflags ::= SEQUENCE OF RPM_UINT32_TYPE

id-rpm-tag-Fileusername	OBJECT_IDENTIFIER ::= { id-rpm-tag 1039 }
Fileusername ::= SEQUENCE OF RPM_STRING_ARRAY_TYPE

id-rpm-tag-Filegroupname	OBJECT_IDENTIFIER ::= { id-rpm-tag 1040 }
Filegroupname ::= SEQUENCE OF RPM_STRING_ARRAY_TYPE

id-rpm-tag-Icon	OBJECT_IDENTIFIER ::= { id-rpm-tag 1043 }
Icon ::= RPM_BIN_TYPE

id-rpm-tag-Sourcerpm	OBJECT_IDENTIFIER ::= { id-rpm-tag 1044 }
Sourcerpm ::= RPM_STRING_TYPE

id-rpm-tag-Fileverifyflags	OBJECT_IDENTIFIER ::= { id-rpm-tag 1045 }
Fileverifyflags ::= SEQUENCE OF RPM_UINT32_TYPE

id-rpm-tag-Archivesize	OBJECT_IDENTIFIER ::= { id-rpm-tag 1046 }
Archivesize ::= RPM_UINT32_TYPE

id-rpm-tag-Providename	OBJECT_IDENTIFIER ::= { id-rpm-tag 1047 }
Providename ::= SEQUENCE OF RPM_STRING_ARRAY_TYPE

id-rpm-tag-Requireflags	OBJECT_IDENTIFIER ::= { id-rpm-tag 1048 }
Requireflags ::= SEQUENCE OF RPM_UINT32_TYPE

id-rpm-tag-Requirename	OBJECT_IDENTIFIER ::= { id-rpm-tag 1049 }
Requirename ::= SEQUENCE OF RPM_STRING_ARRAY_TYPE

id-rpm-tag-Requireversion	OBJECT_IDENTIFIER ::= { id-rpm-tag 1050 }
Requireversion ::= SEQUENCE OF RPM_STRING_ARRAY_TYPE

id-rpm-tag-Conflictflags	OBJECT_IDENTIFIER ::= { id-rpm-tag 1053 }
Conflictflags ::= SEQUENCE OF RPM_UINT32_TYPE

id-rpm-tag-Conflictname	OBJECT_IDENTIFIER ::= { id-rpm-tag 1054 }
Conflictname ::= SEQUENCE OF RPM_STRING_ARRAY_TYPE

id-rpm-tag-Conflictversion	OBJECT_IDENTIFIER ::= { id-rpm-tag 1055 }
Conflictversion ::= SEQUENCE OF RPM_STRING_ARRAY_TYPE

id-rpm-tag-Excludearch	OBJECT_IDENTIFIER ::= { id-rpm-tag 1059 }
Excludearch ::= SEQUENCE OF RPM_STRING_ARRAY_TYPE

id-rpm-tag-Excludeos	OBJECT_IDENTIFIER ::= { id-rpm-tag 1060 }
Excludeos ::= SEQUENCE OF RPM_STRING_ARRAY_TYPE

id-rpm-tag-Exclusivearch	OBJECT_IDENTIFIER ::= { id-rpm-tag 1061 }
Exclusivearch ::= SEQUENCE OF RPM_STRING_ARRAY_TYPE

id-rpm-tag-Exclusiveos	OBJECT_IDENTIFIER ::= { id-rpm-tag 1062 }
Exclusiveos ::= SEQUENCE OF RPM_STRING_ARRAY_TYPE

id-rpm-tag-Rpmversion	OBJECT_IDENTIFIER ::= { id-rpm-tag 1064 }
Rpmversion ::= RPM_STRING_TYPE

id-rpm-tag-Triggerscripts	OBJECT_IDENTIFIER ::= { id-rpm-tag 1065 }
Triggerscripts ::= SEQUENCE OF RPM_STRING_ARRAY_TYPE

id-rpm-tag-Triggername	OBJECT_IDENTIFIER ::= { id-rpm-tag 1066 }
Triggername ::= SEQUENCE OF RPM_STRING_ARRAY_TYPE

id-rpm-tag-Triggerversion	OBJECT_IDENTIFIER ::= { id-rpm-tag 1067 }
Triggerversion ::= SEQUENCE OF RPM_STRING_ARRAY_TYPE

id-rpm-tag-Triggerflags	OBJECT_IDENTIFIER ::= { id-rpm-tag 1068 }
Triggerflags ::= SEQUENCE OF RPM_UINT32_TYPE

id-rpm-tag-Triggerindex	OBJECT_IDENTIFIER ::= { id-rpm-tag 1069 }
Triggerindex ::= SEQUENCE OF RPM_UINT32_TYPE

id-rpm-tag-Verifyscript	OBJECT_IDENTIFIER ::= { id-rpm-tag 1079 }
Verifyscript ::= RPM_STRING_TYPE

id-rpm-tag-Changelogtime	OBJECT_IDENTIFIER ::= { id-rpm-tag 1080 }
Changelogtime ::= SEQUENCE OF RPM_UTCTIME_TYPE

id-rpm-tag-Changelogname	OBJECT_IDENTIFIER ::= { id-rpm-tag 1081 }
Changelogname ::= SEQUENCE OF RPM_STRING_ARRAY_TYPE

id-rpm-tag-Changelogtext	OBJECT_IDENTIFIER ::= { id-rpm-tag 1082 }
Changelogtext ::= SEQUENCE OF RPM_STRING_ARRAY_TYPE

id-rpm-tag-Preinprog	OBJECT_IDENTIFIER ::= { id-rpm-tag 1085 }
Preinprog ::= RPM_STRING_TYPE

id-rpm-tag-Postinprog	OBJECT_IDENTIFIER ::= { id-rpm-tag 1086 }
Postinprog ::= RPM_STRING_TYPE

id-rpm-tag-Preunprog	OBJECT_IDENTIFIER ::= { id-rpm-tag 1087 }
Preunprog ::= RPM_STRING_TYPE

id-rpm-tag-Postunprog	OBJECT_IDENTIFIER ::= { id-rpm-tag 1088 }
Postunprog ::= RPM_STRING_TYPE

id-rpm-tag-Buildarchs	OBJECT_IDENTIFIER ::= { id-rpm-tag 1089 }
Buildarchs ::= SEQUENCE OF RPM_STRING_ARRAY_TYPE

id-rpm-tag-Obsoletename	OBJECT_IDENTIFIER ::= { id-rpm-tag 1090 }
Obsoletename ::= SEQUENCE OF RPM_STRING_ARRAY_TYPE

id-rpm-tag-Verifyscriptprog	OBJECT_IDENTIFIER ::= { id-rpm-tag 1091 }
Verifyscriptprog ::= RPM_STRING_TYPE

id-rpm-tag-Triggerscriptprog	OBJECT_IDENTIFIER ::= { id-rpm-tag 1092 }
Triggerscriptprog ::= SEQUENCE OF RPM_STRING_ARRAY_TYPE

id-rpm-tag-Cookie	OBJECT_IDENTIFIER ::= { id-rpm-tag 1094 }
Cookie ::= RPM_STRING_TYPE

id-rpm-tag-Filedevices	OBJECT_IDENTIFIER ::= { id-rpm-tag 1095 }
Filedevices ::= SEQUENCE OF RPM_UINT32_TYPE

id-rpm-tag-Fileinodes	OBJECT_IDENTIFIER ::= { id-rpm-tag 1096 }
Fileinodes ::= SEQUENCE OF RPM_UINT32_TYPE

id-rpm-tag-Filelangs	OBJECT_IDENTIFIER ::= { id-rpm-tag 1097 }
Filelangs ::= SEQUENCE OF RPM_STRING_ARRAY_TYPE

id-rpm-tag-Prefixes	OBJECT_IDENTIFIER ::= { id-rpm-tag 1098 }
Prefixes ::= SEQUENCE OF RPM_STRING_ARRAY_TYPE

id-rpm-tag-Instprefixes	OBJECT_IDENTIFIER ::= { id-rpm-tag 1099 }
Instprefixes ::= SEQUENCE OF RPM_STRING_ARRAY_TYPE

id-rpm-tag-Capability	OBJECT_IDENTIFIER ::= { id-rpm-tag 1105 }
Capability ::= RPM_UINT32_TYPE

id-rpm-tag-Sourcepackage	OBJECT_IDENTIFIER ::= { id-rpm-tag 1106 }
Sourcepackage ::= RPM_UINT32_TYPE

id-rpm-tag-Buildmacros	OBJECT_IDENTIFIER ::= { id-rpm-tag 1111 }
Buildmacros ::= SEQUENCE OF RPM_STRING_ARRAY_TYPE

id-rpm-tag-Provideflags	OBJECT_IDENTIFIER ::= { id-rpm-tag 1112 }
Provideflags ::= SEQUENCE OF RPM_UINT32_TYPE

id-rpm-tag-Provideversion	OBJECT_IDENTIFIER ::= { id-rpm-tag 1113 }
Provideversion ::= SEQUENCE OF RPM_STRING_ARRAY_TYPE

id-rpm-tag-Obsoleteflags	OBJECT_IDENTIFIER ::= { id-rpm-tag 1114 }
Obsoleteflags ::= SEQUENCE OF RPM_UINT32_TYPE

id-rpm-tag-Obsoleteversion	OBJECT_IDENTIFIER ::= { id-rpm-tag 1115 }
Obsoleteversion ::= SEQUENCE OF RPM_STRING_ARRAY_TYPE

id-rpm-tag-Dirindexes	OBJECT_IDENTIFIER ::= { id-rpm-tag 1116 }
Dirindexes ::= SEQUENCE OF RPM_UINT32_TYPE

id-rpm-tag-Basenames	OBJECT_IDENTIFIER ::= { id-rpm-tag 1117 }
Basenames ::= SEQUENCE OF RPM_STRING_ARRAY_TYPE

id-rpm-tag-Dirnames	OBJECT_IDENTIFIER ::= { id-rpm-tag 1118 }
Dirnames ::= SEQUENCE OF RPM_STRING_ARRAY_TYPE

id-rpm-tag-Origdirindexes	OBJECT_IDENTIFIER ::= { id-rpm-tag 1119 }
Origdirindexes ::= SEQUENCE OF RPM_UINT32_TYPE

id-rpm-tag-Origbasenames	OBJECT_IDENTIFIER ::= { id-rpm-tag 1120 }
Origbasenames ::= SEQUENCE OF RPM_STRING_ARRAY_TYPE

id-rpm-tag-Origdirnames	OBJECT_IDENTIFIER ::= { id-rpm-tag 1121 }
Origdirnames ::= SEQUENCE OF RPM_STRING_ARRAY_TYPE

id-rpm-tag-Optflags	OBJECT_IDENTIFIER ::= { id-rpm-tag 1122 }
Optflags ::= RPM_STRING_TYPE

id-rpm-tag-Disturl	OBJECT_IDENTIFIER ::= { id-rpm-tag 1123 }
Disturl ::= RPM_STRING_TYPE

id-rpm-tag-Payloadformat	OBJECT_IDENTIFIER ::= { id-rpm-tag 1124 }
Payloadformat ::= RPM_STRING_TYPE

id-rpm-tag-Payloadcompressor	OBJECT_IDENTIFIER ::= { id-rpm-tag 1125 }
Payloadcompressor ::= RPM_STRING_TYPE

id-rpm-tag-Payloadflags	OBJECT_IDENTIFIER ::= { id-rpm-tag 1126 }
Payloadflags ::= RPM_STRING_TYPE

id-rpm-tag-Installcolor	OBJECT_IDENTIFIER ::= { id-rpm-tag 1127 }
Installcolor ::= RPM_UINT32_TYPE

id-rpm-tag-Installtid	OBJECT_IDENTIFIER ::= { id-rpm-tag 1128 }
Installtid ::= SEQUENCE OF RPM_UINT32_TYPE

id-rpm-tag-Removetid	OBJECT_IDENTIFIER ::= { id-rpm-tag 1129 }
Removetid ::= SEQUENCE OF RPM_UINT32_TYPE

id-rpm-tag-Rhnplatform	OBJECT_IDENTIFIER ::= { id-rpm-tag 1131 }
Rhnplatform ::= RPM_STRING_TYPE

id-rpm-tag-Platform	OBJECT_IDENTIFIER ::= { id-rpm-tag 1132 }
Platform ::= RPM_STRING_TYPE

id-rpm-tag-Patchesname	OBJECT_IDENTIFIER ::= { id-rpm-tag 1133 }
Patchesname ::= SEQUENCE OF RPM_STRING_ARRAY_TYPE

id-rpm-tag-Patchesflags	OBJECT_IDENTIFIER ::= { id-rpm-tag 1134 }
Patchesflags ::= SEQUENCE OF RPM_UINT32_TYPE

id-rpm-tag-Patchesversion	OBJECT_IDENTIFIER ::= { id-rpm-tag 1135 }
Patchesversion ::= SEQUENCE OF RPM_STRING_ARRAY_TYPE

id-rpm-tag-Cachectime	OBJECT_IDENTIFIER ::= { id-rpm-tag 1136 }
Cachectime ::= RPM_UINT32_TYPE

id-rpm-tag-Cachepkgpath	OBJECT_IDENTIFIER ::= { id-rpm-tag 1137 }
Cachepkgpath ::= RPM_STRING_TYPE

id-rpm-tag-Cachepkgsize	OBJECT_IDENTIFIER ::= { id-rpm-tag 1138 }
Cachepkgsize ::= RPM_UINT32_TYPE

id-rpm-tag-Cachepkgmtime	OBJECT_IDENTIFIER ::= { id-rpm-tag 1139 }
Cachepkgmtime ::= RPM_UINT32_TYPE

id-rpm-tag-Filecolors	OBJECT_IDENTIFIER ::= { id-rpm-tag 1140 }
Filecolors ::= SEQUENCE OF RPM_UINT32_TYPE

id-rpm-tag-Fileclass	OBJECT_IDENTIFIER ::= { id-rpm-tag 1141 }
Fileclass ::= SEQUENCE OF RPM_UINT32_TYPE

id-rpm-tag-Classdict	OBJECT_IDENTIFIER ::= { id-rpm-tag 1142 }
Classdict ::= SEQUENCE OF RPM_STRING_ARRAY_TYPE

id-rpm-tag-Filedependsx	OBJECT_IDENTIFIER ::= { id-rpm-tag 1143 }
Filedependsx ::= SEQUENCE OF RPM_UINT32_TYPE

id-rpm-tag-Filedependsn	OBJECT_IDENTIFIER ::= { id-rpm-tag 1144 }
Filedependsn ::= SEQUENCE OF RPM_UINT32_TYPE

id-rpm-tag-Dependsdict	OBJECT_IDENTIFIER ::= { id-rpm-tag 1145 }
Dependsdict ::= SEQUENCE OF RPM_UINT32_TYPE

id-rpm-tag-Sourcepkgid	OBJECT_IDENTIFIER ::= { id-rpm-tag 1146 }
Sourcepkgid ::= RPM_BIN_TYPE

id-rpm-tag-Filecontexts	OBJECT_IDENTIFIER ::= { id-rpm-tag 1147 }
Filecontexts ::= SEQUENCE OF RPM_STRING_ARRAY_TYPE

id-rpm-tag-Fscontexts	OBJECT_IDENTIFIER ::= { id-rpm-tag 1148 }
Fscontexts ::= SEQUENCE OF RPM_STRING_ARRAY_TYPE

id-rpm-tag-Recontexts	OBJECT_IDENTIFIER ::= { id-rpm-tag 1149 }
Recontexts ::= SEQUENCE OF RPM_STRING_ARRAY_TYPE

id-rpm-tag-Policies	OBJECT_IDENTIFIER ::= { id-rpm-tag 1150 }
Policies ::= SEQUENCE OF RPM_STRING_ARRAY_TYPE

id-rpm-tag-Pretrans	OBJECT_IDENTIFIER ::= { id-rpm-tag 1151 }
Pretrans ::= RPM_STRING_TYPE

id-rpm-tag-Posttrans	OBJECT_IDENTIFIER ::= { id-rpm-tag 1152 }
Posttrans ::= RPM_STRING_TYPE

id-rpm-tag-Pretransprog	OBJECT_IDENTIFIER ::= { id-rpm-tag 1153 }
Pretransprog ::= RPM_STRING_TYPE

id-rpm-tag-Posttransprog	OBJECT_IDENTIFIER ::= { id-rpm-tag 1154 }
Posttransprog ::= RPM_STRING_TYPE

id-rpm-tag-Disttag	OBJECT_IDENTIFIER ::= { id-rpm-tag 1155 }
Disttag ::= RPM_STRING_TYPE

id-rpm-tag-Suggestsname	OBJECT_IDENTIFIER ::= { id-rpm-tag 1156 }
Suggestsname ::= SEQUENCE OF RPM_STRING_ARRAY_TYPE

id-rpm-tag-Suggestsversion	OBJECT_IDENTIFIER ::= { id-rpm-tag 1157 }
Suggestsversion ::= SEQUENCE OF RPM_STRING_ARRAY_TYPE

id-rpm-tag-Suggestsflags	OBJECT_IDENTIFIER ::= { id-rpm-tag 1158 }
Suggestsflags ::= SEQUENCE OF RPM_UINT32_TYPE

id-rpm-tag-Enhancesname	OBJECT_IDENTIFIER ::= { id-rpm-tag 1159 }
Enhancesname ::= SEQUENCE OF RPM_STRING_ARRAY_TYPE

id-rpm-tag-Enhancesversion	OBJECT_IDENTIFIER ::= { id-rpm-tag 1160 }
Enhancesversion ::= SEQUENCE OF RPM_STRING_ARRAY_TYPE

id-rpm-tag-Enhancesflags	OBJECT_IDENTIFIER ::= { id-rpm-tag 1161 }
Enhancesflags ::= SEQUENCE OF RPM_UINT32_TYPE

id-rpm-tag-Priority	OBJECT_IDENTIFIER ::= { id-rpm-tag 1162 }
Priority ::= SEQUENCE OF RPM_UINT32_TYPE

id-rpm-tag-Cvsid	OBJECT_IDENTIFIER ::= { id-rpm-tag 1163 }
Cvsid ::= RPM_STRING_TYPE

id-rpm-tag-Blinkpkgid	OBJECT_IDENTIFIER ::= { id-rpm-tag 1164 }
Blinkpkgid ::= SEQUENCE OF RPM_STRING_ARRAY_TYPE

id-rpm-tag-Blinkhdrid	OBJECT_IDENTIFIER ::= { id-rpm-tag 1165 }
Blinkhdrid ::= SEQUENCE OF RPM_STRING_ARRAY_TYPE

id-rpm-tag-Blinknevra	OBJECT_IDENTIFIER ::= { id-rpm-tag 1166 }
Blinknevra ::= SEQUENCE OF RPM_STRING_ARRAY_TYPE

id-rpm-tag-Flinkpkgid	OBJECT_IDENTIFIER ::= { id-rpm-tag 1167 }
Flinkpkgid ::= SEQUENCE OF RPM_STRING_ARRAY_TYPE

id-rpm-tag-Flinkhdrid	OBJECT_IDENTIFIER ::= { id-rpm-tag 1168 }
Flinkhdrid ::= SEQUENCE OF RPM_STRING_ARRAY_TYPE

id-rpm-tag-Flinknevra	OBJECT_IDENTIFIER ::= { id-rpm-tag 1169 }
Flinknevra ::= SEQUENCE OF RPM_STRING_ARRAY_TYPE

id-rpm-tag-Packageorigin	OBJECT_IDENTIFIER ::= { id-rpm-tag 1170 }
Packageorigin ::= RPM_STRING_TYPE

id-rpm-tag-Scriptstates	OBJECT_IDENTIFIER ::= { id-rpm-tag 1174 }
Scriptstates ::= SEQUENCE OF RPM_UINT32_TYPE

id-rpm-tag-Scriptmetrics	OBJECT_IDENTIFIER ::= { id-rpm-tag 1175 }
Scriptmetrics ::= SEQUENCE OF RPM_UINT32_TYPE

id-rpm-tag-Buildcpuclock	OBJECT_IDENTIFIER ::= { id-rpm-tag 1176 }
Buildcpuclock ::= RPM_UINT32_TYPE

id-rpm-tag-Filedigestalgos	OBJECT_IDENTIFIER ::= { id-rpm-tag 1177 }
Filedigestalgos ::= SEQUENCE OF RPM_UINT32_TYPE

id-rpm-tag-Variants	OBJECT_IDENTIFIER ::= { id-rpm-tag 1178 }
Variants ::= SEQUENCE OF RPM_STRING_ARRAY_TYPE

id-rpm-tag-Xmajor	OBJECT_IDENTIFIER ::= { id-rpm-tag 1179 }
Xmajor ::= RPM_UINT32_TYPE

id-rpm-tag-Xminor	OBJECT_IDENTIFIER ::= { id-rpm-tag 1180 }
Xminor ::= RPM_UINT32_TYPE

id-rpm-tag-Repotag	OBJECT_IDENTIFIER ::= { id-rpm-tag 1181 }
Repotag ::= RPM_STRING_TYPE

id-rpm-tag-Keywords	OBJECT_IDENTIFIER ::= { id-rpm-tag 1182 }
Keywords ::= SEQUENCE OF RPM_STRING_ARRAY_TYPE

id-rpm-tag-Buildplatforms	OBJECT_IDENTIFIER ::= { id-rpm-tag 1183 }
Buildplatforms ::= SEQUENCE OF RPM_STRING_ARRAY_TYPE

id-rpm-tag-Packagecolor	OBJECT_IDENTIFIER ::= { id-rpm-tag 1184 }
Packagecolor ::= RPM_UINT32_TYPE

id-rpm-tag-Packageprefcolor	OBJECT_IDENTIFIER ::= { id-rpm-tag 1185 }
Packageprefcolor ::= RPM_UINT32_TYPE

id-rpm-tag-Xattrsdict	OBJECT_IDENTIFIER ::= { id-rpm-tag 1186 }
Xattrsdict ::= SEQUENCE OF RPM_STRING_ARRAY_TYPE

id-rpm-tag-Filexattrsx	OBJECT_IDENTIFIER ::= { id-rpm-tag 1187 }
Filexattrsx ::= SEQUENCE OF RPM_UINT32_TYPE

id-rpm-tag-Depattrsdict	OBJECT_IDENTIFIER ::= { id-rpm-tag 1188 }
Depattrsdict ::= SEQUENCE OF RPM_STRING_ARRAY_TYPE

id-rpm-tag-Conflictattrsx	OBJECT_IDENTIFIER ::= { id-rpm-tag 1189 }
Conflictattrsx ::= SEQUENCE OF RPM_UINT32_TYPE

id-rpm-tag-Obsoleteattrsx	OBJECT_IDENTIFIER ::= { id-rpm-tag 1190 }
Obsoleteattrsx ::= SEQUENCE OF RPM_UINT32_TYPE

id-rpm-tag-Provideattrsx	OBJECT_IDENTIFIER ::= { id-rpm-tag 1191 }
Provideattrsx ::= SEQUENCE OF RPM_UINT32_TYPE

id-rpm-tag-Requireattrsx	OBJECT_IDENTIFIER ::= { id-rpm-tag 1192 }
Requireattrsx ::= SEQUENCE OF RPM_UINT32_TYPE

id-rpm-tag-Dbinstance	OBJECT_IDENTIFIER ::= { id-rpm-tag 1195 }
Dbinstance ::= RPM_UINT32_TYPE

id-rpm-tag-Nvra	OBJECT_IDENTIFIER ::= { id-rpm-tag 1196 }
Nvra ::= RPM_STRING_TYPE

id-rpm-tag-Filepaths	OBJECT_IDENTIFIER ::= { id-rpm-tag 1197 }
Filepaths ::= SEQUENCE OF RPM_STRING_ARRAY_TYPE

id-rpm-tag-Origpaths	OBJECT_IDENTIFIER ::= { id-rpm-tag 1198 }
Origpaths ::= SEQUENCE OF RPM_STRING_ARRAY_TYPE

id-rpm-tag-Rpmlibversion	OBJECT_IDENTIFIER ::= { id-rpm-tag 1199 }
Rpmlibversion ::= RPM_UINT32_TYPE

id-rpm-tag-Rpmlibtimestamp	OBJECT_IDENTIFIER ::= { id-rpm-tag 1200 }
Rpmlibtimestamp ::= RPM_UINT32_TYPE

id-rpm-tag-Rpmlibvendor	OBJECT_IDENTIFIER ::= { id-rpm-tag 1201 }
Rpmlibvendor ::= RPM_UINT32_TYPE

id-rpm-tag-Class	OBJECT_IDENTIFIER ::= { id-rpm-tag 1202 }
Class ::= RPM_STRING_TYPE

id-rpm-tag-Sanitycheck	OBJECT_IDENTIFIER ::= { id-rpm-tag 1205 }
Sanitycheck ::= RPM_STRING_TYPE

id-rpm-tag-Sanitycheckprog	OBJECT_IDENTIFIER ::= { id-rpm-tag 1206 }
Sanitycheckprog ::= RPM_STRING_TYPE

id-rpm-tag-Filestat	OBJECT_IDENTIFIER ::= { id-rpm-tag 1207 }
Filestat ::= SEQUENCE OF RPM_STRING_ARRAY_TYPE

id-rpm-tag-Stat	OBJECT_IDENTIFIER ::= { id-rpm-tag 1208 }
Stat ::= SEQUENCE OF RPM_STRING_ARRAY_TYPE

id-rpm-tag-Origintid	OBJECT_IDENTIFIER ::= { id-rpm-tag 1209 }
Origintid ::= SEQUENCE OF RPM_UINT32_TYPE

id-rpm-tag-Origintime	OBJECT_IDENTIFIER ::= { id-rpm-tag 1210 }
Origintime ::= SEQUENCE OF RPM_UINT32_TYPE

id-rpm-tag-Headerstartoff	OBJECT_IDENTIFIER ::= { id-rpm-tag 1211 }
Headerstartoff ::= RPM_UINT64_TYPE

id-rpm-tag-Headerendoff	OBJECT_IDENTIFIER ::= { id-rpm-tag 1212 }
Headerendoff ::= RPM_UINT64_TYPE

id-rpm-tag-Packagetime	OBJECT_IDENTIFIER ::= { id-rpm-tag 1213 }
Packagetime ::= RPM_UINT64_TYPE

id-rpm-tag-Packagesize	OBJECT_IDENTIFIER ::= { id-rpm-tag 1214 }
Packagesize ::= RPM_UINT64_TYPE

id-rpm-tag-Packagedigest	OBJECT_IDENTIFIER ::= { id-rpm-tag 1215 }
Packagedigest ::= RPM_STRING_TYPE

id-rpm-tag-Packagestat	OBJECT_IDENTIFIER ::= { id-rpm-tag 1216 }
Packagestat ::= RPM_BIN_TYPE

id-rpm-tag-Packagebaseurl	OBJECT_IDENTIFIER ::= { id-rpm-tag 1217 }
Packagebaseurl ::= RPM_STRING_TYPE

id-rpm-tag-Distepoch	OBJECT_IDENTIFIER ::= { id-rpm-tag 1218 }
Distepoch ::= RPM_STRING_TYPE

id-rpm-tag-Conflictyamlentry	OBJECT_IDENTIFIER ::= { id-rpm-tag 1219 }
Conflictyamlentry ::= SEQUENCE OF RPM_STRING_ARRAY_TYPE

id-rpm-tag-Obsoleteyamlentry	OBJECT_IDENTIFIER ::= { id-rpm-tag 1220 }
Obsoleteyamlentry ::= SEQUENCE OF RPM_STRING_ARRAY_TYPE

id-rpm-tag-Provideyamlentry	OBJECT_IDENTIFIER ::= { id-rpm-tag 1221 }
Provideyamlentry ::= SEQUENCE OF RPM_STRING_ARRAY_TYPE

id-rpm-tag-Requireyamlentry	OBJECT_IDENTIFIER ::= { id-rpm-tag 1222 }
Requireyamlentry ::= SEQUENCE OF RPM_STRING_ARRAY_TYPE

id-rpm-tag-Filedigestalgo	OBJECT_IDENTIFIER ::= { id-rpm-tag 5011 }
Filedigestalgo ::= RPM_UINT32_TYPE

id-rpm-tag-Bugurl	OBJECT_IDENTIFIER ::= { id-rpm-tag 5012 }
Bugurl ::= RPM_STRING_TYPE


-- RPM package header (from file)
Package ::= SEQUENCE {
  name                Name,
  epoch               Epoch           DEFAULT 0,
  version             Version,
  release             Release,
  summary             Summary,
  description         Description,
  buildtime           Buildtime,
  buildhost           Buildhost,
  size                Size,
  license             License,
  group               Group,
  os                  Os,
  arch                Arch,
  filesizes           Filesizes,
  filemodes           Filemodes,
  filerdevs           Filerdevs,
  filemtimes          Filemtimes,
  filedigests         Filedigests,
  filelinktos         Filelinktos,
  fileflags           Fileflags,
  fileusername        Fileusername,
  filegroupname       Filegroupname,
  sourcerpm           Sourcerpm,
  fileverifyflags     Fileverifyflags,
  archivesize         Archivesize,
  providename         Providename,
  requireflags        Requireflags,
  requirename         Requirename,
  requireversion      Requireversion,
  rpmversion          Rpmversion,
  changelogtime       Changelogtime,
  changelogname       Changelogname,
  changelogtext       Changelogtext,
  cookie              Cookie,
  filedevices         Filedevices,
  fileinodes          Fileinodes,
  filelangs           Filelangs,
  provideflags        Provideflags,
  provideversion      Provideversion,
  dirindexes          Dirindexes,
  basenames           Basenames,
  dirnames            Dirnames,
  optflags            Optflags,
  payloadformat       Payloadformat,
  payloadcompressor   Payloadcompressor,
  payloadflags        Payloadflags,
  platform            Platform,
  filecolors          Filecolors,
  fileclass           Fileclass,
  classdict           Classdict,
  filedependsx        Filedependsx,
  filedependsn        Filedependsn,
  dependsdict         Dependsdict,
  filecontexts        Filecontexts,
  filedigestalgos     Filedigestalgos,
  rpmlibversion       Rpmlibversion,
  rpmlibtimestamp     Rpmlibtimestamp,
  rpmlibvendor        Rpmlibvendor
}
END
